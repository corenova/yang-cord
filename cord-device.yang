module cord-device {
  namespace "urn:cord:device";
  prefix cord-dev;
  yang-version 1.1;

  organization
   "Open Networking Lab (CORD) / Corenova Technologies";

  contact
    "Larry Peterson <llp@onlab.us>
     Peter K. Lee <peter@corenova.com>";
  
  import ietf-yang-types { prefix yang; }
  
  revision 2016-07-14 {
    description "Initial revision.";
  }

  typedef bandwidth {
    type unit32;
    range 1000000..max; // should be at least 1 Mbps?
    units 'bps';
  }
  
  grouping device {
    leaf mac { type yang:mac-address; mandatory true; }
    leaf identity { type string; }

    leaf subscriber {
      type instance-identifier;
      config false;
    }
    
    container features {
      // how are the uplink/downlink speeds defined here related to 'subscriber'?
      leaf uplink-speed {
        type bandwidth;
        default 1000000000;      
      }
      leaf downlink-speed {
        type bandwidth;
        default 1000000000;      
      }
      action update;
    }
    action save;
  }
}
