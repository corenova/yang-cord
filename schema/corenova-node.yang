module corenova-node {
  namespace "urn:corenova:node";
  prefix node;

  organization
    "Corenova Technologies, Inc.";

  contact
    "Peter K. Lee <peter@corenova.com>";

  description
    "This module defines extensions to dynamically control schema node
     display and access overlay controls";

  feature corenova-node {
    description
      "this is to indicate the agent supports dynamic schema node
       link/map/view.";
  }
    
  extension link {
    description
      "Links the current leaf (or leaf-list) to an alternate leaf in the
       schema data tree. The current leaf becomes a 'mirror' instance
       of the target node.";
    argument target-node-path {
      yin-element true;
    }
  }

  extension map {
    description
      "Maps the current container (or list entry) to an alternate container
       in the schema data tree. The target-node-path must not map to
       leaf or leaf-list nodes. The current container will map to
       additional data nodes found inside the alternate container. The
       mapped data nodes behave similarly to the 'link' extension
       case. It can be defined one or more times within the same
       container to map across modules and other subtrees.";
    argument target-node-path {
      yin-element true;
    }
  }

  extension view {
    description
      "Informs the interface layers that only the data nodes referenced
       within the value argument should be made visible to the
       consumer.";
    argument value;
  }
}
