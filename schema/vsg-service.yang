module vsg-service {
  namespace "urn:ietf:params:xml:ns:yang:vsg-service";
  prefix vsg;
  yang-version 1.1;

  import ietf-yang-types { prefix yang; }
  import xos-core        { prefix xos; }
  import xos-slice       { prefix xslice; }
  import xos-types       { prefix xtype; }
  import volt-service    { prefix volt; }

  organization
    "Open Networking Lab (CORD) / Corenova Technologies";

  contact
    "Larry Peterson <llp@onlab.us>
     Peter K. Lee <peter@corenova.com>";

  revision 2016-09-09 {
    description "Initial revision.";
  }

  identity virtual-subscriber-gateway { base xos:service; }

  typedef subscriber-inflow {
    description
      "Valid subscriber input flow for VSG service can be:
       - VOLT flow
       - VSG flow (chaining)
       - other generic flow ID";
    type union {
      type volt:subscriber-outflow;
      type vsg:subscriber-outflow;
      type yang:uuid;
    }
  }
  typedef subscriber-outflow {
    type leafref {
      path "/vsg:controller/vsg:port/vsg:id";
    }
  }

  /*
   * Groupings
   */ 
  grouping gateways-list {
    grouping subscriber-gateway {
      leaf id { type xtype:unique-identifier; }
      
      container services {
        description
          "Contains various services provided by the gateway.";
        container cdn {
          if-feature cdn;
        }
        container firewall {
          if-feature firewall;
          leaf-list rules { type string; }
        }
        container url-filter {
          if-feature url-filter;
          leaf level {
            type enumeration {
              enum "PG";
              // others...
            }
          }
          leaf-list rules { type string; }
        }
        container uverse {
          if-feature uverse;
        }
      }
      list flow {
        description
          "Each flow represents a subscriber flow into the VSG instance.";
        leaf id {
          type yang:uuid;
        }
      }
    }
    list gateway {
      description
        "Each entry represents a VSG instance.";
      key id;
      uses subscriber-gateway;
    }
  }
  grouping subscriber {
    description
      "This grouping represents a VSG service subscriber along with
       reference to fabric flows used by the subscriber.";

    leaf status {
      type enumeration {
        enum "enabled" {
          description "Enabled";
          value 1;
        }
        enum "suspended" {
          description "Suspended";
        }
        enum "delinquent" {
          description "Delinquent";
        }
        enum "violation" {
          description "Copyright Violation";
        }
      }
      default enabled;
    }
    leaf demo { type boolean; default false; }
    leaf uplink-speed   { type volt:bandwidth; }
    leaf downlink-speed { type volt:bandwidth; }
    leaf inflow {
      description
        "Represents a unique flow identifier from the fabric that the
         subscriber connects into the VSG service.";
      type vsg:subscriber-inflow;
    }
    leaf outflow {
      description
        "Represents a unique flow identifier from the VSG service that the
         subscriber uses to connect into the fabric.";
      config false;
      type vsg:subscriber-outflow;
    }
  }
  
  /*
   * Configuration data
   */
  container controller {
    description
      "The controller configuration represents a VSG controller which manages
       multiple VSG gateways. The VSG controller provides agregate
       abstraction of the entire NFaaS as a single switch to the
       network fabric. Each port entry of the controller represents
       each VSG subscriber flow as a distinct openflow port.";
    uses xos:service {
      refine kind { default virtual-subscriber-gateway; }
      augment "subscriber" { uses vsg:subscriber; }
    }
    container slice {
      uses xslice:slice;
    }
    uses gateways-list {
      augment gateway {
        leaf instance {
          type leafref {
            path "../../../slice/instances";
          }
        }
      }
    }
    list port {
      description
        "Each entry represents a VSG subscriber flow connected across VSG
         gateways.";
      key id;
      leaf id {
        description "OpenFlow Port ID";
        type yang:uuid;
        mandatory true;
      }
      leaf link {
        type leafref {
          path '../../gateway/flow/id';
        }
        mandatory true;
      }
    }
  }
}
