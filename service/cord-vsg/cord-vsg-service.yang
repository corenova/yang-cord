module cord-vsg-service {
  namespace "urn:ietf:params:xml:ns:yang:cord-vsg-service";
  prefix vsg;
  yang-version 1.1;

  import xos-controller    { prefix xos; }
  import xos-slice         { prefix xslice; }
  import xos-types         { prefix xtype; }
  import cord-tenant       { prefix cord; }
  import cord-volt-service { prefix volt; }

  organization
    "Open Networking Lab (CORD) / Corenova Technologies";

  contact
    "Larry Peterson <llp@onlab.us>
     Peter K. Lee <peter@corenova.com>";

  revision 2016-09-09 {
    description "Initial revision.";
  }

  identity virtual-subscriber-gateway { base xos:xos-service; }

  /*
   * Type definitions
   */
  typedef subscriber-inflow {
    description
      "Valid subscriber input flow for VSG service can be:
       - VOLT flow
       - VSG flow (chaining)
       - other generic flow ID";
    type union {
      type volt:subscriber-outflow;
      type vsg:subscriber-outflow;
      type xtype:flow-identifier;
    }
  }
  typedef subscriber-outflow {
    type leafref {
      path "/vsg:controller/vsg:port/vsg:id";
    }
  }

  /*
   * Groupings
   */ 
  grouping gateways-list {
    grouping subscriber-gateway {
      leaf id { type xtype:unique-identifier; }
      
      container features {
        description
          "Contains various features provided by the gateway.";
        container firewall {
          if-feature firewall;
          leaf enabled {
            type boolean;
            default false;
          }
          leaf-list rules { type string; }
        }
        container url-filter {
          if-feature url-filter;
          leaf enabled {
            type boolean;
            default false;
          }
          leaf level {
            type enumeration {
              enum "PG";
              // others...
            }
          }
          leaf-list rules { type string; }
        }
        container uverse {
          if-feature uverse;
          leaf enabled {
            type boolean;
            default false;
          }
        }
      }
      list flow {
        description
          "Each flow represents a subscriber flow into the VSG instance.";
        leaf id {
          type xtype:flow-identifier;
        }
      }
    }
    list gateway {
      description
        "Each entry represents a VSG instance.";
      key id;
      uses subscriber-gateway;
    }
  }
  grouping subscriber {
    description
      "This grouping represents a VSG service subscriber along with
       reference to fabric flows used by the subscriber.";

    leaf inflow {
      description
        "Represents a unique flow identifier from the fabric that the
         subscriber connects into the VSG service.";
      type vsg:subscriber-inflow;
    }
    leaf outflow {
      description
        "Represents a unique flow identifier from the VSG service that the
         subscriber uses to connect into the fabric.";
      config false;
      type vsg:subscriber-outflow;
    }
  }
  
  /*
   * Configuration data
   */
  container controller {
    description
      "The controller configuration represents a VSG controller which manages
       multiple VSG gateways. The VSG controller provides agregate
       abstraction of the entire NFaaS as a single switch to the
       network fabric. Each port entry of the controller represents
       each VSG subscriber flow as a distinct openflow port.";
    uses xos:service {
      refine kind { default virtual-subscriber-gateway; }
      augment "subscriber" { uses vsg:subscriber; }
    }
    container slice {
      uses xslice:slice;
    }
    uses gateways-list {
      augment gateway {
        leaf instance {
          type leafref {
            path "/vsg:controller/slice/instances";
          }
        }
      }
    }
    list port {
      description
        "Each entry represents a VSG subscriber flow connected across VSG
         gateways.";
      key id;
      leaf id {
        description "OpenFlow Port ID";
        type xtype:flow-identifier;
        mandatory true;
      }
      leaf link {
        type leafref {
          path '/vsg:controller/gateway/flow/id';
        }
        mandatory true;
      }
    }
  }
  /*
   * Augmentations to XOS
   */
  augment "/xos:tenant/cord:cord/cord:subscriber" {
    container service {
      leaf id {
        type leafref {
          path "/vsg:controller/subscriber/id";
        }
      }
      leaf gateway {
        config false;
        type leafref {
          path "/vsg:controller/gateway/id";
        }
      }
      leaf firewall {
        type boolean;
        default false;
      }
      leaf url-filter {
        type boolean;
        default false;
      }
      leaf uverse {
        type boolean;
        default false;
      }
    }
  }
}
